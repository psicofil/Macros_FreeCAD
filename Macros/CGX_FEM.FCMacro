# -*- coding: utf-8 -*-
## CGX PostProccesing in FreeCAD
# Author: Gomez Lucio
# Modified by: PrzemoF
# License: LGPL v 2.1
# Version: 24/04/2016

########### CONFIGURATION ###########

# Linux
use_xterm = 0 # Do you want use xterm? 1 if yes, 0 if no (only work in Linux)
cgx_bin = '/home/lucio/Calculix/cgx_2.9 ' # CGX binary exapmle for Linux

# Windows
# cgx_bin = '"C:\\Program Files (x86)\\bConverged\\CalculiX\\cgx\\cgx "' # CGX binary example for windows

########### START MACRO #############

import FreeCADGui
import FreeCAD
from PySide import QtCore, QtGui
from platform import system

selection = FreeCADGui.Selection.getSelection()
if len(selection) == 1:
    sel = selection[0]
    # print '\nSelected Object: ' ,sel.Name
    if hasattr(sel,"Proxy") and sel.Proxy.Type == 'FemAnalysis':
        # print sel.Name
        analysis = sel
        for m in analysis.Member:
            if m.isDerivedFrom("Fem::FemMeshObject"):
                filename = m.Name
                break
        else: # for loop runs through all members but no mesh found
            print 'No Mesh --> No Output'
        ccxoutputdir = sel.OutList[0].WorkingDir
        from platform import system
        if system() == "Linux":
            filename = ccxoutputdir + '/' + filename + '.frd'
            cgxcommand =cgx_bin +' -v ' + filename
            print cgxcommand
            #import subprocess
            process = QtCore.QProcess()
            try:
                process = QtCore.QProcess()
                if use_xterm == 1:
                    process.startDetached('xterm -e ' + cgxcommand)
                else:
                    process.startDetached(cgxcommand)
                FreeCAD.Console.PrintMessage('Running '+ cgxcommand)
            except:
                FreeCAD.Console.PrintError('Error!!, sorry..')
                QtGui.QMessageBox.critical(None,'Error','Error!!, Sorry.Please report the error in the FreeCAD forum',QtGui.QMessageBox.Abort)
        elif system() == "Windows":
            path_sep = "\\"     
            filename = ccxoutputdir + '\\' + filename + '.frd'
            cgxcommand =cgx_bin +' -v ' + filename
            #import subprocess
            process = QtCore.QProcess()
            try:
                process = QtCore.QProcess()
                process.startDetached(cgxcommand)
                FreeCAD.Console.PrintMessage('Running '+ cgxcommand)
            except:
                FreeCAD.Console.PrintError('Error!!, sorry..')
                QtGui.QMessageBox.critical(None,'Error','Error!!, Sorry.Please report the error in the FreeCAD forum',QtGui.QMessageBox.Abort)            
        else:
            print "Your OS is ", system(), ", which is not yet supported !"
            QtGui.QMessageBox.critical(None,'Error',"Your OS is ", system(), ", which is not yet supported !",QtGui.QMessageBox.Abort)
    else:
        print 'Select a MechanicalAnalysis Object'
        QtGui.QMessageBox.information(None,'Information','Select a MechanicalAnalysis Object',QtGui.QMessageBox.Abort)
else:
   print 'Select one MechanicalAnalysis Object'
   QtGui.QMessageBox.information(None,'Information','Select a MechanicalAnalysis Object',QtGui.QMessageBox.Abort)
